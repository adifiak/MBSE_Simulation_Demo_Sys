package SimulationElementCatalog{
    connection def MechanicalConnection{
        end base;
        end attached;
    }

    port def SpeedReferencePort{}

    port def PositionPort{}

    port def AnglePort{}
}
